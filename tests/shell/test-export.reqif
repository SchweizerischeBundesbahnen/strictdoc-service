# Documentation export by StrictDoc

# Specification: Test Document

## R1: Test Section (SECTION)

### REQ-001: First Requirement (REQUIREMENT)
This is a test requirement
- STATUS: Draft

### REQ-002: Second Requirement (REQUIREMENT)
This is another test requirement
- STATUS: Approved
