[DOCUMENT]
TITLE: Test Document

[SECTION]
TITLE: Test Section

[REQUIREMENT]
UID: REQ-001
STATUS: Draft
TITLE: First Requirement
STATEMENT: >>>
This is a test requirement
<<<

[REQUIREMENT]
UID: REQ-002
STATUS: Approved
TITLE: Second Requirement
STATEMENT: >>>
This is another test requirement
<<<

[/SECTION]
